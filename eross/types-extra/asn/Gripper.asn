--------------------------------------------------------------------------------
--- ASN.1 message definitions for EROSS extra types (PIAP E.E. Gripper)
---
--- Copyright (C) 2017      Stiftelsen SINTEF
--- Copyright (C) 2018-2020 SINTEF AS
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

Gripper-Types DEFINITIONS ::=
BEGIN

GripperState ::= ENUMERATED
{
  error(-1),
  disabled(0),
  standby(1),
  open(2),
  capturing(3),
  captured(4),
  releasing(5)
}

GripperCMD ::= ENUMERATED
{
  disable(0),
  enable(1),
  capture(2),
  release(3),
  stop(4)
}

END

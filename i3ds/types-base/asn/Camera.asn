--------------------------------------------------------------------------------
--- ASN.1 message definitions for the I3DS sensor suite.
---
--- Copyright (C) 2017      Stiftelsen SINTEF
--- Copyright (C) 2018-2019 SINTEF AS
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

Camera-Types DEFINITIONS ::=
BEGIN
IMPORTS PlanarRegion FROM Region-Types
T-UInt8, T-UInt32, T-Boolean FROM TASTE-BasicTypes
T-Float, T-UInt16 FROM TASTE-ExtendedTypes;

--- Shutter time in microseconds
ShutterTime ::= T-UInt32

--- Sensor gain in decibel, range is camera dependent
SensorGain ::= T-Float

--- Camera exposure command.
CameraExposure ::=
SEQUENCE
{
    shutter    ShutterTime,
    gain       SensorGain
}

--- Camera auto exposure command.
CameraAutoExposure ::=
SEQUENCE
{
    enable         T-Boolean,
    max-shutter    ShutterTime,
    max-gain       SensorGain
}

--- Flash strength from 0 (off) to 255 (full)
FlashStrength ::= T-UInt8

--- Camera flash illumination command.
CameraFlash ::=
SEQUENCE
{
    enable     T-Boolean,
    strength   FlashStrength
}

--- Camera region command.
CameraRegion ::=
SEQUENCE
{
    enable   T-Boolean,
    region   PlanarRegion
}

--- Illumination pattern sequence, range depends on camera
PatternSequence ::= T-UInt16

--- Illumination pattern ID, 0 is none, range depends on camera
PatternID ::= T-UInt16

--- Camera pattern illumination command.
CameraPattern ::=
SEQUENCE
{
    enable             T-Boolean,
    pattern-sequence   PatternSequence
}

--- Camera sequence, instruct camera to take a series of N images (> 0),
--- enable=False yields continous shot when camera is started
ImageSequence ::= T-UInt32
CameraImgSequence ::=
SEQUENCE
{
    enable            T-Boolean,
    image-sequence    ImageSequence
}

--- Camera configuration.
CameraConfiguration ::=
SEQUENCE
{
   shutter                 ShutterTime,
   gain                    SensorGain,
   auto-exposure-enabled   T-Boolean,
   max-shutter             ShutterTime,
   max-gain                SensorGain,
   region-enabled          T-Boolean,
   region                  PlanarRegion,
   flash-enabled           T-Boolean,
   flash-strength          FlashStrength,
   pattern-enabled         T-Boolean,
   pattern-sequence        PatternSequence,
   image-sequence-enabled  T-Boolean,
   image-sequence          ImageSequence,
   image-max-sequence      ImageSequence
}

END

--------------------------------------------------------------------------------
--- ASN.1 message definitions for the I3DS sensor suite.
---
--- Copyright (C) 2017      Stiftelsen SINTEF
--- Copyright (C) 2018-2019 SINTEF AS
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

PointCloud-Types DEFINITIONS ::=
BEGIN
IMPORTS SampleAttributes FROM SampleAttribute-Types
PlanarRegion FROM Region-Types
T-UInt32,T-Boolean FROM TASTE-BasicTypes
T-UInt16 FROM TASTE-ExtendedTypes;

--- Point fields format adapted from PCD.
Point-format-t ::=
ENUMERATED
{
   fields-xyz-f   -- Point XYZ as floating-point in meter
}

--- Point-cloud descriptor as simplified version of PCD.
PointCloudDescriptor ::=
SEQUENCE
{
   attributes     SampleAttributes,  -- Sample attributes.
   point-format   Point-format-t,    -- Point field format, currently only XYZ as float.
   point-size     T-UInt16,          -- Point size in bytes including alignment padding.
   width          T-UInt32,          -- Width of point-cloud.
   height         T-UInt32           -- Height of point-cloud, 1 when unorganized.
}

-- PointCloud sensor mode command
PointCloudSensorMode ::=
ENUMERATED
{
    mode-undefined,
    mode-camera,                     -- operate as regular camera
    mode-camera-oneshot,             -- operate as regular camera, but only one image
    mode-structured-light            -- Mode to use with SINTEFs Structured Light projector
}

PointCloudMode ::=
SEQUENCE
{
    mode          PointCloudSensorMode,
    enable-flash  T-Boolean
}

PointCloudAcquire ::=
SEQUENCE
{
   -- only relevant in 3D-mode, this will also forward the images used
   -- to generate the pointcloud if there are any camera-clients
   -- attached to the sensor
   publish-images T-Boolean
}

END

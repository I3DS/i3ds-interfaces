--------------------------------------------------------------------------------
--- ASN.1 message definitions for the I3DS sensor suite.
---
--- Copyright (C) 2018      SINTEF AS
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

Common-Types DEFINITIONS ::=
BEGIN
IMPORTS T-String, T-Int64 FROM TASTE-ExtendedTypes;

--- The node ID is a 24-bit integer identifying a node in the suite (such as a sensor).
NodeID ::= INTEGER(0 .. 16777215)

--- The endpoint ID is a 8-bit integer identifying the endpoint within the node.
EndpointID ::= INTEGER(0 .. 255)

--- The timepoint type is a 64-bit count of microseconds since the system-defined epoch.
Timepoint ::= T-Int64

--- Command result codes.
ResultCode ::=
ENUMERATED
{
   success,            -- Successfully executed the request.
   error-node-id,      -- The node ID was not recognized.
   error-endpoint-id,  -- The endpoint ID was not recognized.
   error-unsupported,  -- The requested operation is not supported.
   error-state,        -- The requested operation is illegal from current state.
   error-value,        -- One or more of the provided values are illegal or in conflict.
   error-other         -- Other error, see message.
}

--- Command response common for all nodes classes.
CommandResponse ::=
SEQUENCE
{
   result   ResultCode,
   message  T-String
}

END

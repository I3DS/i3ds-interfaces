--------------------------------------------------------------------------------
--- ASN.1 message definitions for the I3DS sensor suite.
---
--- Copyright (C) 2019      SINTEF AS
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

PoseEstimator-Types DEFINITIONS ::=
BEGIN
IMPORTS SampleAttributes FROM SampleAttribute-Types
T-Boolean, T-UInt8 FROM TASTE-BasicTypes
Base-Pose FROM Base-Types;


--- Pose estimator mode (false - tracking, true - imaging)
PoseEstimatorImagingMode ::=
SEQUENCE
{
   imaging-mode   T-Boolean
}

--- Pose estimator camera select
PoseEstimatorCameraSelect ::=
SEQUENCE
{
   camera-select   T-UInt8
}

--- Pose estimator configuration.
PoseEstimatorConfiguration ::=
SEQUENCE
{
   imaging-mode    T-Boolean,
   camera-select   T-UInt8
}

--- Pose estimator measurement.
PoseEstimatorMeasurement ::=
SEQUENCE
{
   attributes       SampleAttributes,
   estimated-pose   Base-Pose
}

END

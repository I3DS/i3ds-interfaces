--------------------------------------------------------------------------------
--- ASN.1 message definitions for the I3DS sensor suite.
---
--- Copyright (C) 2017      Stiftelsen SINTEF
--- Copyright (C) 2018-2019 SINTEF AS
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

Sensor-Types DEFINITIONS ::=
BEGIN
IMPORTS T-UInt32 FROM TASTE-BasicTypes
T-String FROM TASTE-ExtendedTypes
Base-Temperature FROM Base-Types;

--------------------------------------------------------------------------------
---  State of operation for sensors and corresponding commands and _events_
--------------------------------------------------------------------------------
---
---  SENSOR      = INACTIVE,
---  INACTIVE    = (activate   -> STANDBY),
---  STANDBY     = (start      -> OPERATIONAL
---                |deactivate -> INACTIVE
---                |_failure_  -> FAILURE),
---  OPERATIONAL = (stop       -> STANDBY,
---                |_count_    -> STANDBY,
---                |_failure_  -> FAILURE),
---  FAILURE     = (_restore_  -> STANDBY
---                |deactivate -> INACTIVE).
--------------------------------------------------------------------------------
SensorState  ::= ENUMERATED {inactive, standby, operational, failure}
StateCommand ::= ENUMERATED {activate, start, stop, deactivate}

-- Sensor status message is common for all sensor classes.
SensorStatus ::=
SEQUENCE
{
   current-state        SensorState,
   device-temperature   Base-Temperature
}

-- Sample period given as microseconds between sample messages, 0 is aperiodic.
SamplePeriod ::= T-UInt32

-- Sample batch size per message, where default is 1.
BatchSize ::= T-UInt32

-- Sample batches to acquire, where 0 is inifinite.
BatchCount ::= T-UInt32

--- Sample command common for all sensor classes.
SampleCommand ::=
SEQUENCE
{
   period        SamplePeriod,  -- Period of batch samples when operational.
   batch-size    BatchSize,     -- Number of samples in each batch.
   batch-count   BatchCount     -- Number of batches to acquire when operational.
}

--- Sensor configuration common for all sensor classes.
SensorConfiguration ::=
SEQUENCE
{
   device-name   T-String,      -- String identifying the sensor device.
   period        SamplePeriod,  -- Period of batch samples when operational.
   batch-size    BatchSize,     -- Number of samples in each batch.
   batch-count   BatchCount     -- Number of batches to acquire when operational.
}

END

--------------------------------------------------------------------------------
--- ASN.1 message definitions for the I3DS sensor suite.
---
--- Copyright (C) 2017      Stiftelsen SINTEF
--- Copyright (C) 2018-2019 SINTEF AS
---
--- This program is free software; you can redistribute it and/or
--- modify it under the terms of the GNU General Public License
--- as published by the Free Software Foundation; either version 2
--- of the License, or (at your option) any later version.
---
--- This program is distributed in the hope that it will be useful,
--- but WITHOUT ANY WARRANTY; without even the implied warranty of
--- MERCHANTABILITY or FITNESS FOR A PARTICULAR PURPOSE.  See the
--- GNU General Public License for more details.
---
--- You should have received a copy of the GNU General Public License
--- along with this program;  if not, see <http://www.gnu.org/licenses/>.
--------------------------------------------------------------------------------

DepthMap-Types DEFINITIONS ::=
BEGIN
IMPORTS SampleAttributes FROM SampleAttribute-Types
PlanarRegion FROM Region-Types
T-UInt8 FROM TASTE-BasicTypes
T-Float, T-UInt16 FROM TASTE-ExtendedTypes;

--- Depth format.
Depth-format-t ::=
ENUMERATED
{
   depth-f -- Depth as floating-point meter, NaN is invalid
}

--- Depth-map descriptor as simplified version of PCD.
DepthMapDescriptor ::=
SEQUENCE
{
   attributes    SampleAttributes,  -- Sample attributes.
   depth-format  Depth-format-t,    -- Depth format, currently only floating-point
   depth-size    T-UInt8,           -- Depth size in bytes, currently 4
   width         T-UInt16,          -- Width of depth-map.
   height        T-UInt16           -- Height of depth-map.
}

END
